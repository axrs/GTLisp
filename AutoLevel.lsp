(DEFUN c:autolevel (/ $point)
    (SETQ $point (gt:m2p))
    (COMMAND "INSERT" "GTAUTOLEVEL" $point 0.75 0 "")
    (PRINC)
)
(DEFUN gt:m2p (/ pt1 pt2)
    (SETQ pt1 (GETPOINT "\nEnter first point: "))
    (SETQ pt2 (GETPOINT pt1 "\nEnter second point: "))
    (POLAR pt1 (ANGLE pt1 pt2) (/ (DISTANCE pt1 pt2) 2.0))
)
