(DEFUN gtmembers:parse ($file / $line $sub $list $i)
  (IF (AND (SETQ $file (FINDFILE $file)) (SETQ $file (OPEN $file "r")))
    (PROGN
      (WHILE (SETQ $line (READ-LINE $file))
	(COND
	  (
	   (WCMATCH $line "`[*`]")
	   (IF $sub
	     (SETQ $list (CONS (REVERSE $sub) $list))
	   )
	   (SETQ $sub (LIST (SUBSTR $line 2 (- (STRLEN $line) 2))))
	  )

	  (
	   (WCMATCH $line "*=*")
	   (SETQ $i 0)
	   (WHILE (/= "=" (SUBSTR $line (SETQ $i (1+ $i)) 1)))
	   (SETQ $sub (CONS (LIST (SUBSTR $line 1 (1- $i)) (SUBSTR $line (1+ $i))) $sub))
	  )
	  ((SETQ $sub (CONS (LIST $line) $sub)))
	)
      )
      (CLOSE $file)
      (IF $sub
	(SETQ $list (CONS (REVERSE $sub) $list))
      )
    )
  )
  (REVERSE $list)
)

(DEFUN c:gtmembers (/ *error* $updatelist $members $dclhandle)

    ;;=-=-=-=-=-=-=-=-=-=-=-=-=-=-=-=-=-=-=-=-=-=-=-=-=-=-=-=-=-=-=-=-=-=-=-=-=-=-;;
    ;|
    <function>*error*</function>
    <summary>Error trapping and variable restoration for the gtmembers method.</sumary>
    <param name="message">Error message generated by AutoCAD.</param>
    <returns>Nothing</returns>
    |;
    ;;=-=-=-=-=-=-=-=-=-=-=-=-=-=-=-=-=-=-=-=-=-=-=-=-=-=-=-=-=-=-=-=-=-=-=-=-=-=-;; 
    (DEFUN *error* (message)
        (IF $dclhandle
            (UNLOAD_DIALOG $dclhandle)
        )
        (OR (WCMATCH (STRCASE message) "*BREAK,*CANCEL*,*EXIT*")
            (PRINC (STRCAT "\n** Error: " message " **"))
        )
        (PRINC)
    )
    ;;=-=-=-=-=-=-=-=-=-=-=-=-=-=-=-=-=-=-=-=-=-=-=-=-=-=-=-=-=-=-=-=-=-=-=-=-=-=-;;
    ;|
    <function>UpdateList</function>
    <summary>Updates a list box with the associated $key to the values within the specified list.</sumary>
    <param name="$key">List box identifier 'key' to update.</param>
    <param name="$list">Proposed contents of the list box.</param>
    <returns>Nothing</returns>
    |;
    ;;=-=-=-=-=-=-=-=-=-=-=-=-=-=-=-=-=-=-=-=-=-=-=-=-=-=-=-=-=-=-=-=-=-=-=-=-=-=-;; 
    (DEFUN gtmembers:updatelist ($key $list)
        (START_LIST $key)
        (MAPCAR 'ADD_LIST $list)
        (END_LIST)
    )
    ;;=-=-=-=-=-=-=-=-=-=-=-=-=-=-=-=-=-=-=-=-=-=-=-=-=-=-=-=-=-=-=-=-=-=-=-=-=-=-;;
    ;|
    <function>gtmembers:dialog</function>
    <summary>Creates and displays the GTMembers dialog.</sumary>
    <returns></returns>
    |;
    ;;=-=-=-=-=-=-=-=-=-=-=-=-=-=-=-=-=-=-=-=-=-=-=-=-=-=-=-=-=-=-=-=-=-=-=-=-=-=-;;
    (DEFUN gtmembers:dialog (/ $result x $dclid $filename $fileid)
        ;;Create the Dialog File
        (IF (AND (SETQ $filename (VL-FILENAME-MKTEMP "Members.dcl")) (SETQ $fileid (OPEN $filename "w")))
            (PROGN (FOREACH x (LIST
                                  "gt_members : dialog {"
                                  "	  label = \"GTMembers - Structural Sections\";"
                                  "   : row{"
                                  "	      : boxed_column{"
                                  "         label=\"Section Properties:\";"
                                  "           : popup_list {"
                                  "               key = \"members\";"
                                  "               label = \"\";"
                                  "               width = 20;"
                                  "               fixed_width=true;"
                                  "               value = \"\";"
                                  "		  alignment=centered;"
                                  "           }"
                                  "           spacer;"
                                  "		  : list_box {"
                                  "		      label=\"Section Size:\";"
                                  "		      key=\"size\";"
                                  "		      width=20;"
                                  "		      value=\"\";"
                                  "                   fixed_width=true;"
                                  "		      alignment=centered;"
                                  "	          }"
                                  "       }"
                                  "	  : boxed_column{"
                                  "           label=\"Drawing Properties:\";"
                                  "           width = 50;"
                                  "	  }"
                                  "   }"
                                  " ok_cancel;"
                                  "}"
                              )
                       (PRINC x $fileid)
                       (WRITE-LINE "" $fileid)
                   )
                   (CLOSE $fileid)
            )
        )

        ;;Show the dialog and get a reponse
        (COND ((SETQ $dclid (LOAD_DIALOG $filename))
               (NEW_DIALOG "gt_members" $dclid)
               ;;On the popup list change
               (ACTION_TILE
                   "members"
                   (STRCAT
                       "(gtmembers:updatelist \"size\")"
                       ""
                   )
               )

               (ACTION_TILE
                   "accept"
                   "(SETQ $result T)(done_dialog)"
               )
               (START_DIALOG)
               (UNLOAD_DIALOG $dclid)
               (VL-FILE-DELETE $filename)
               (IF $result
                   $result
                   nil
               )
              )
              (T nil)
        )
    )
)
