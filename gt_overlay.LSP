(DEFUN gtoverlay:vector_text (str col / c i l v y)

  (SETQ	v
	 '(
	   (" ")
	   ("\t")
	   ("!" 45 45 65 135)
	   ("\"" 104 134 107 137)
	   ("#" 43 63 46 66 84 94 87 97 115 135 118 138 72 78 103 109)
	   ("$"	25 35 52 52 43 47 58 78	83 87 92 112 123 127 118 118 135
	    135)
	   ("%"	 52   52   63	63   74	  74   85   85	 96   96   107
	    107	 118  118  129	129  47	  48   67   68	 56   56   59
	    59	 113  114  133	134  122  122  125  125
	   )
	   ("&"	 43   46   49	49   52	  72   57   58	 67   68   76
	    76	 79   79   83	83   85	  85   94   94	 103  123  134
	    136	 127  127
	   )
	   ("'" 105 135)
	   ("(" 17 17 26 36 45 105 116 126 137 137)
	   (")" 14 14 25 35 46 106 115 125 134 134)
	   ("*" 73 74 76 77 84 86 92 98 104 106 113 114 116 117)
	   ("+" 55 115 82 84 86 88)
	   ("," 34 35 45 46 55 57)
	   ("-" 83 88)
	   ("." 45 46 55 56)
	   ("/" 52 52 63 63 74 74 85 85 96 96 107 107 118 118 129 129)
	   ("0" 44 47 134 137 53 123 58 128)
	   ("1" 44 48 124 125 56 136)
	   ("2"	43 48 53 53 64 64 75 75	86 86 97 97 108	128 134	137 123
	    123)
	   ("3" 53 53 44 47 58 88 95 97 108 128 134 137 123 123)
	   ("4" 46 48 57 137 78 78 73 76 83 83 94 94 105 115 126 126)
	   ("5" 53 53 44 47 58 88 94 97 93 133 134 138)
	   ("6" 44 47 58 88 95 97 84 84 53 113 124 124 135 137)
	   ("7" 44 54 65 75 86 96 107 117 128 138 133 137 123 123)
	   ("8" 44 47 94 97 134 137 53 83 58 88 103 123 108 128)
	   ("9" 44 46 57 57 68 128 97 97 84 86 134 137 93 123)
	   (":" 45 46 55 56 95 96 105 106)
	   (";" 34 35 45 46 55 57 95 96 105 106)
	   ("<"	47 47 56 56 65 65 74 74	83 83 94 94 105	105 116	116 127
	    127)
	   ("=" 73 78 93 98)
	   (">"	43 43 54 54 65 65 76 76	87 87 96 96 105	105 114	114 123
	    123)
	   ("?" 45 45 65 75 86 86 97 97 108 128 134 137 123 123)
	   ("@"	 34   38   43	43   52	  112  123  123	 134  137  128
	    128	 79   119  68	68   65	  66   105  106	 77   107  74
	    94
	   )
	   ("A"	41 43 47 49 52 62 58 68	73 77 83 93 87 97 104 114 106
	    116	125 135	133 134)
	   ("B" 42 47 53 123 58 88 108 128 94 97 132 137)
	   ("C"	44 47 53 53 58 58 62 112 123 123 134 136 127 127 108 138)
	   ("D" 42 46 57 57 127 127 132 136 68 118 53 123)
	   ("E" 42 48 58 58 94 95 86 106 132 137 128 138 53 123)
	   ("F" 42 45 94 95 86 106 132 137 128 138 53 123)
	   ("G"	44 47 53 53 58 78 86 89	62 112 123 123 134 136 127 127
	    108	138)
	   ("H" 41 43 47 49 131 133 137 139 93 97 52 122 58 128)
	   ("I" 43 47 133 137 55 125)
	   ("J" 52 62 43 46 57 127 135 139)
	   ("K"	 42   44   48	49   132  134  136  138	 53   123  84
	    85	 95   95   106	116  127  127  76   76	 67   67   58
	    58
	   )
	   ("L" 42 47 48 58 53 123 132 135)
	   ("M"	41 43 47 49 52 122 58 128 131 132 138 139 103 113 107
	    117	84 94 86 96 65 75)
	   ("N"	41 44 131 132 136 139 52 122 48	128 113	113 94 104 85 85
	    66 76 57 57)
	   ("O"	44 46 53 53 57 57 123 123 127 127 134 136 62 112 68 118)
	   ("P" 42 45 84 87 132 137 53 123 98 128)
	   ("Q"	134 136	123 123	127 127	112 62 118 68 53 53 57 57 44 46
	    35 36 23 24	27 28)
	   ("R"	42 44 48 49 132	137 123	53 128 98 84 87	76 76 67 67 58
	    58)
	   ("S"	42 62 53 53 44 47 58 78	86 87 93 95 102	122 133	136 127
	    127	118 138)
	   ("T" 43 47 55 125 132 138 131 121 139 129)
	   ("U" 44 46 52 53 57 58 62 122 68 128 131 133 137 139)
	   ("V"	45 55 64 74 66 76 83 103 87 107	112 122	118 128	131 133
	    137	139)
	   ("W"	43 63 47 67 72 92 74 94	76 96 78 98 101	121 105	115 109
	    129	131 132	138 139)
	   ("X"	 41   43   47	49   131  133  137  139	 52   52   58
	    58	 63   63   67	67   74	  74   76   76	 85   95   104
	    104	 106  106  113	113  117  117  122  122	 128  128
	   )
	   ("Y"	43 47 55 85 94 94 96 96	103 113	107 117	122 122	128 128
	    131	133 137	139)
	   ("Z"	122 122	58 58 132 138 42 48 128	128 52 52 63 63	74 74 85
	    95 106 106 117 117)
	   ("[" 15 17 135 137 25 125)
	   ("\\" 122 122 113 113 104 104 95 95 86 86 77 77 68 68 59 59)
	   ("]" 14 16 134 136 26 126)
	   ("^"	102 102	113 113	124 124	135 135	126 126	117 117	108 108)
	   ("_" 21 29)
	   ("`" 125 125 134 134)
	   ("a" 43 46 48 48 52 72 57 97 83 86 103 106)
	   ("b"	42 43 45 46 54 54 57 58	68 98 97 97 105	106 94 94 132
	    132	53 133)
	   ("c" 44 46 53 53 57 58 52 92 93 93 104 106 97 98 108 108)
	   ("d"	44 45 47 48 52 92 53 53	56 56 93 93 104	105 96 96 136
	    136	57 137)
	   ("e"	44 46 53 53 57 58 52 92	93 93 104 106 97 98 88 88 73 78)
	   ("f" 43 46 54 124 93 93 95 96 135 137 128 128)
	   ("g"	13 16 22 32 27 97 107 108 66 66	96 96 54 55 104	105 63
	    63 93 93 62	92)
	   ("h" 42 44 46 48 57 97 53 133 132 132 94 94 105 106)
	   ("i" 43 47 55 105 103 104 135 135)
	   ("j" 22 22 13 15 26 106 104 105 136 136)
	   ("k"	42 44 46 48 53 133 132 132 57 57 66 66 74 75 85	85 96
	    106	107 108)
	   ("l" 43 47 55 135 133 134)
	   ("m"	41 43 45 46 48 49 52 102 55 105	58 108 101 101 93 93 104
	    104	96 96 107 107)
	   ("n" 42 44 46 48 53 103 57 97 102 102 94 94 105 106)
	   ("o" 44 46 104 106 53 53 57 57 93 93 97 97 52 92 58 98)
	   ("p"	12 15 23 103 102 102 54	54 94 94 45 46 105 106 57 58 97
	    98 68 88)
	   ("q"	15 18 27 107 108 108 56	56 96 96 44 45 104 105 52 53 92
	    93 62 82)
	   ("r" 42 46 54 104 102 103 95 95 106 108 99 99)
	   ("s" 52 52 43 47 58 68 73 77 82 92 103 107 98 98)
	   ("t" 45 47 58 58 54 124 102 103 105 107)
	   ("u" 102 102 106 106 53 103 56 56 44 45 47 107 48 48)
	   ("v"	45 45 54 64 56 66 73 83	77 87 92 92 98 98 101 103 107
	    109)
	   ("w"	43 53 47 57 62 92 64 84	66 86 68 98 101	103 95 105 107
	    109)
	   ("x"	42 44 46 48 102	104 106	108 53 53 57 57	93 93 97 97 64
	    64 66 66 84	84 86 86 75 75)
	   ("y"	12 13 24 24 35 45 54 64	56 66 73 83 77 87 92 92	98 98
	    101	103 107	109)
	   ("z"	92 92 58 58 102	108 42 48 97 97	86 86 75 75 64 64 53 53)
	   ("{" 16 17 25 65 73 74 85 125 136 137)
	   ("|" 15 135)
	   ("}" 14 15 26 66 77 78 86 126 134 135)
	   ("~" 112 122 133 134 125 125 116 117 128 138)
	   ("‘" 114 116 125 126 136 137)
	   ("’" 114 115 125 126 135 137)
	   ("¡" 45 115 135 135)
	   ("¢"	26 36 45 47 58 58 54 54	53 93 94 94 98 98 105 107 116
	    126)
	   ("£" 43 48 54 74 83 86 94 94 103 123 134 136 117 127)
	   ("¤"	83 83 88 88 133	133 138	138 94 97 124 127 104 114 107
	    117)
	   ("¥"	 44   46   55	75   81	  89   94   94	 96   96   101
	    103	 107  109  113	113  117  117  122  122	 128  128  131
	    133	 137  139
	   )
	   ("¦" 15 55 95 135)
	   ("§"	 42   42   32	36   47	  47   56   57	 65   65   74
	    74	 83   83   92	102  68	  78   87   87	 96   96   105
	    105	 113  114  123	123  134  138  128  128
	   )
	   ("¨" 134 134 137 137)
	   ("©"	 54   57   63	63   68	  68   72   122	 79   129  133
	    133	 138  138  144	147  75	  76   87   87	 84   114  125
	    126	 117  117
	   )
	   ("ª" 63 67 84 86 88 88 93 103 97 127 114 116 134 136)
	   ("«"	 55   55   64	64   73	  73   82   82	 93   93   104
	    104	 115  115  58	58   67	  67   76   76	 85   85   96
	    96	 107  107  118	118
	   )
	   ("¬" 68 98 92 97)
	   ("­" 83 88)
	   ("®"	 54   57   63	63   68	  68   72   122	 79   129  133
	    133	 138  138  144	147  74	  124  95   96	 125  126  77
	    87	 107  117
	   )
	   ("¯" 151 159)
	   ("°" 105 106 114 124 117 127 135 136)
	   ("±" 42 48 92 98 65 85 105 125)
	   ("²" 84 87 95 95 106 106 117 127 135 136 124 124)
	   ("³" 94 94 85 86 97 107 116 116 127 127 135 136 124 124)
	   ("´" 125 125 136 136)
	   ("µ" 12 12 23 113 44 47 49 49 58 118)
	   ("¶"	45 45 49 49 48 128 46 126 133 139 122 125 112 115 102
	    105	92 95 83 85)
	   ("·" 85 86 95 96)
	   ("¸" 14 15 26 26 35 35)
	   ("¹" 84 86 124 124 95 135)
	   ("º" 63 67 84 86 134 136 93 123 97 127)
	   ("»"	 52   52   63	63   74	  74   85   85	 94   94   103
	    103	 112  112  55	55   66	  66   77   77	 88   88   97
	    97	 106  106  115	115
	   )
	   ("¼"	 48   98   59	59   55	  57   65   65	 76   76   87
	    87	 83   133  122	122  52	  52   63   63	 74   74   85
	    85	 96   96   107	107  118  118  129  129
	   )
	   ("½"	 46   49   57	57   68	  68   79   89	 97   98   86
	    86	 83   133  122	122  52	  52   63   63	 74   74   85
	    85	 96   96   107	107  118  118  129  129
	   )
	   ("¾"	 48   98   59	59   55	  57   65   65	 76   76   87
	    87	 92   92   83	84   95	  105  114  114	 125  125  133
	    134	 122  122  52	52   63	  63   74   74	 85   85   96
	    96	 107  107  118	118  129  129
	   )
	   ("¿" 44 47 58 58 53 73 84 84 95 95 106 116 136 136)
	   ("À"	 41   43   47	49   52	  62   58   68	 73   77   83
	    93	 87   97   104	114  106  116  125  135	 133  134  155
	    155	 164  164
	   )
	   ("Á"	 41   43   47	49   52	  62   58   68	 73   77   83
	    93	 87   97   104	114  106  116  125  135	 133  134  155
	    155	 166  166
	   )
	   ("Â"	 41   43   47	49   52	  62   58   68	 73   77   83
	    93	 87   97   104	114  106  116  125  135	 133  134  154
	    154	 165  165  156	156
	   )
	   ("Ã"	 41   43   47	49   52	  62   58   68	 73   77   83
	    93	 87   97   104	114  106  116  125  135	 133  134  152
	    152	 163  165  155	157  168  168
	   )
	   ("Ä"	 41   43   47	49   52	  62   58   68	 73   77   83
	    93	 87   97   104	114  106  116  125  135	 133  134  163
	    163	 167  167
	   )
	   ("Å"	 41   43   47	49   52	  62   58   68	 73   77   83
	    93	 87   97   104	114  106  116  125  135	 133  134  145
	    145	 154  154  165	165  156  156
	   )
	   ("Æ"	 41   43   45	49   52	  62   73   93	 104  114  125
	    125	 84   85   59	59   56	  126  97   98	 88   88   108
	    108	 134  139  129	129
	   )
	   ("Ç"	44 47 53 53 58 58 62 112 123 123 134 136 127 127 108 138
	    14 15 26 26	35 35)
	   ("È"	42 48 58 58 94 95 86 106 132 137 128 138 53 123	156 156
	    165	165)
	   ("É"	42 48 58 58 94 95 86 106 132 137 128 138 53 123	155 155
	    166	166)
	   ("Ê"	42 48 58 58 94 95 86 106 132 137 128 138 53 123	154 154
	    165	166 157	157)
	   ("Ë"	42 48 58 58 94 95 86 106 132 137 128 138 53 123	164 164
	    167	167)
	   ("Ì" 43 47 133 137 55 125 155 155 164 164)
	   ("Í" 43 47 133 137 55 125 155 155 166 166)
	   ("Î" 43 47 133 137 55 125 154 154 165 165 156 156)
	   ("Ï" 43 47 133 137 55 125 163 163 167 167)
	   ("Ð" 42 46 57 57 127 127 132 136 68 118 53 123 91 92 94 95)
	   ("Ñ"	 41   44   131	132  137  139  52   122	 48   128  113
	    113	 94   104  85	85   66	  76   57   57	 152  152  163
	    165	 155  157  168	168
	   )
	   ("Ò"	44 46 53 53 57 57 123 123 127 127 134 136 62 112 68 118
	    155	155 164	164)
	   ("Ó"	44 46 53 53 57 57 123 123 127 127 134 136 62 112 68 118
	    155	155 166	166)
	   ("Ô"	44 46 53 53 57 57 123 123 127 127 134 136 62 112 68 118
	    154	154 165	165 156	156)
	   ("Õ"	 44   46   53	53   57	  57   123  123	 127  127  134
	    136	 62   112  68	118  152  152  163  165	 155  157  168
	    168
	   )
	   ("Ö"	44 46 53 53 57 57 123 123 127 127 134 136 62 112 68 118
	    163	163 167	167)
	   ("×"	 52   52   63	63   74	  74   85   85	 96   96   107
	    107	 118  118  58	58   67	  67   76   76	 94   94   103
	    103	 112  112
	   )
	   ("Ø"	 44   46   53	53   57	  57   123  123	 127  127  134
	    136	 62   112  68	118  43	  43   64   74	 85   95   106
	    116	 137  137
	   )
	   ("Ù"	44 46 52 53 57 58 62 122 68 128	131 133	137 139	155 155
	    164	164)
	   ("Ú"	44 46 52 53 57 58 62 122 68 128	131 133	137 139	155 155
	    166	166)
	   ("Û"	44 46 52 53 57 58 62 122 68 128	131 133	137 139	154 154
	    165	165 156	156)
	   ("Ü"	44 46 52 53 57 58 62 122 68 128	131 133	137 139	163 163
	    167	167)
	   ("Ý"	 44   46   55	85   94	  94   96   96	 103  113  107
	    117	 122  122  128	128  131  133  137  139	 145  155  166
	    166
	   )
	   ("Þ" 42 44 132 132 53 133 74 77 104 107 88 98)
	   ("ß" 42 42 43 123 134 136 107 127 95 96 87 87 58 78 45 47)
	   ("à" 43 46 48 48 52 72 57 97 83 86 103 106 125 125 134 134)
	   ("á" 43 46 48 48 52 72 57 97 83 86 103 106 125 125 136 136)
	   ("â"	43 46 48 48 52 72 57 97	83 86 103 106 124 124 135 135
	    126	126)
	   ("ã"	43 46 48 48 52 72 57 97	83 86 103 106 122 122 133 134
	    125	126 137	137)
	   ("ä" 43 46 48 48 52 72 57 97 83 86 103 106 133 133 137 137)
	   ("å"	43 46 48 48 52 72 57 97	83 86 103 106 125 125 134 134
	    145	145 136	136)
	   ("æ"	42 44 46 48 59 59 51 71	82 84 102 104 55 95 76 79 89 99
	    106	108)
	   ("ç"	14 15 26 26 35 35 44 46	53 53 57 58 52 92 93 93	104 106
	    97 98 108 108)
	   ("è"	44 46 53 53 57 58 52 92	93 93 104 106 97 98 88 88 73 78
	    125	125 134	134)
	   ("é"	44 46 53 53 57 58 52 92	93 93 104 106 97 98 88 88 73 78
	    125	125 136	136)
	   ("ê"	 44   46   53	53   57	  58   52   92	 93   93   104
	    106	 97   98   88	88   73	  78   124  124	 135  135  126
	    126
	   )
	   ("ë"	44 46 53 53 57 58 52 92	93 93 104 106 97 98 88 88 73 78
	    133	133 137	137)
	   ("ì" 43 47 55 105 103 104 125 125 134 134)
	   ("í" 43 47 55 105 103 104 124 124 135 135)
	   ("î" 43 47 55 105 103 104 124 124 135 135 126 126)
	   ("ï" 43 47 55 105 103 104 133 133 136 136)
	   ("ð"	 44   46   53	53   57	  57   52   82	 58   88   83
	    83	 87   107  94	96   116  116  113  114	 125  125  134
	    134	 136  137
	   )
	   ("ñ"	42 44 46 48 53 103 57 97 102 102 94 94 105 106 122 122
	    133	134 125	126 137	137)
	   ("ò"	44 46 104 106 53 53 57 57 93 93	97 97 52 92 58 98 125
	    125	134 134)
	   ("ó"	44 46 104 106 53 53 57 57 93 93	97 97 52 92 58 98 125
	    125	136 136)
	   ("ô"	44 46 104 106 53 53 57 57 93 93	97 97 52 92 58 98 124
	    124	135 135	126 126)
	   ("õ"	 44   46   104	106  53	  53   57   57	 93   93   97
	    97	 52   92   58	98   122  122  133  135	 125  127  138
	    138
	   )
	   ("ö"	44 46 104 106 53 53 57 57 93 93	97 97 52 92 58 98 133
	    133	137 137)
	   ("÷" 55 55 115 115 82 88)
	   ("ø"	44 46 104 106 53 53 57 57 93 93	97 97 52 92 58 98 42 42
	    64 64 75 75	86 86 108 108)
	   ("ù"	102 102	106 106	53 103 56 56 44	45 47 107 48 48	125 125
	    134	134)
	   ("ú"	102 102	106 106	53 103 56 56 44	45 47 107 48 48	125 125
	    136	136)
	   ("û"	102 102	106 106	53 103 56 56 44	45 47 107 48 48	124 124
	    135	135 126	126)
	   ("ü"	102 102	106 106	53 103 56 56 44	45 47 107 48 48	133 133
	    137	137)
	   ("ý"	 12   13   24	24   35	  45   54   64	 56   66   73
	    83	 77   87   92	92   98	  98   101  103	 107  109  125
	    125	 136  136
	   )
	   ("þ"	12 15 132 132 23 133 54	54 45 46 57 58 68 88 94	94 105
	    106	97 98)
	   ("ÿ"	 12   13   24	24   35	  45   54   64	 56   66   73
	    83	 77   87   92	92   98	  98   101  103	 107  109  133
	    133	 137  137
	   )
	  )
  )

  (EVAL
    (LIST 'DEFUN
	  'gtoverlay:vector_text
	  '(str col / c i l v y)
	  (LIST	'SETQ
		'v
		(LIST 'QUOTE
		      (MAPCAR
			(FUNCTION
			  (LAMBDA (b)
			    (CONS (CAR b)
				  (MAPCAR '(LAMBDA (a)
					     (IF a
					       (LIST (REM a 10) (/ a 10))
					     )
					   )
					  (CDR b)
				  )
			    )
			  )
			)
			v
		      )
		)
	  )
	  '(SETQ i 0 y 0)

	  '(REPEAT
	    (STRLEN str)
	    (COND
	     ((EQ (SETQ c (SUBSTR str 1 1)) " ")

	      (SETQ
	       i
	       (+ i 9)
	       str
	       (SUBSTR str 2)
	      )
	     )
	     ((EQ c "\t")

	      (SETQ
	       i
	       (+ i 36)
	       str
	       (SUBSTR str 2)
	      )
	     )
	     ((EQ c "\n")

	      (SETQ
	       i
	       0
	       y
	       (- y 16)
	       str
	       (SUBSTR str 2)
	      )
	     )
	     ((SETQ
	       l
	       (CONS
		(MAPCAR
		 (FUNCTION
		  (LAMBDA (a)
		    (IF
		     a
		     (LIST (+ (CAR a) i) (+ (CADR a) y))
		    )
		  )
		 )
		 (CDR (ASSOC c v))
		)
		l
	       )
	       str
	       (SUBSTR str 2)
	       i
	       (+ i 9)
	      )
	     )
	    )
	   )
	  '(CONS col (APPLY 'APPEND l))
    )
  )

  (gtoverlay:vector_text str col)
)


(DEFUN gtoverlay:message ($message $color / *error* vl g s)
  (DEFUN *error* (msg)
    (OR	(WCMATCH (STRCASE msg) "*BREAK,*CANCEL*,*EXIT*")
	(PRINC (STRCAT "\n** Error: " msg " **"))
    )
    (REDRAW)
    (PRINC)
  )

  (SETQ	vl
	 (gtoverlay:vector_text
	   $message
	   $color
	 )
  )

  (WHILE (= 5 (CAR (SETQ g (GRREAD nil 13 0))))
    (REDRAW)
    (SETQ s (/ (GETVAR 'viewsize) (CADR (GETVAR 'screensize)))
	  g (TRANS (CADR g) 1 3)
    )
    (GRVECS vl
	    (
	     (LAMBDA (r x y)
	       (LIST
		 (LIST r 0. 0. x)
		 (LIST 0. r 0. y)
		 (LIST 0. 0. r 0.)
		 (LIST 0. 0. 0. 1.)
	       )
	     )
	      s
	      (+ (CAR g) (* 15 s))
	      (- (CADR g) (* 31 s))
	    )
    )
  )
  (REDRAW)
  (PRINC)
)


(DEFUN reactor:grdisplay (a b)
  (REDRAW)
  (gtoverlay:displaypoint
    (_toprightpoint)
    (STRCAT
      "DATE: "
      (gtmisc:getdatecustom "DD/MM/YY")
      "\nTIME: "
      (gtmisc:gettime)
      "\n----------------\n"
      (APPLY
	(FUNCTION STRCAT)
	(CDR
	  (APPLY
	    (FUNCTION APPEND)
	    (MAPCAR
	      (FUNCTION
		(LAMBDA	(v)
		  (LIST	"\n"
			(STRCASE v)
			": "
			(VL-PRINC-TO-STRING (GETVAR v))
		  )
		)
	      )
	      '("CLAYER" "CECOLOR" "CELTYPE")
	    )
	  )
	)
      )
      "\n----------------\n"
      (APPLY
	(FUNCTION STRCAT)
	(CDR
	  (APPLY
	    (FUNCTION APPEND)
	    (MAPCAR
	      (FUNCTION
		(LAMBDA	(v)
		  (LIST	"\n"
			(STRCASE v)
			": "
			(VL-PRINC-TO-STRING (GETVAR v))
		  )
		)
	      )
	      '("DIMSCALE" "OSMODE")
	    )
	  )
	)
      )      
    )
    
    (IF	(OR (= (GETVAR "CECOLOR") "BYLAYER")
	    (= (GETVAR "CECOLOR") "BYBLOCK")
	)
      (cdr
	(assoc 62 (entget (tblobjname "layer" (getvar "CLAYER"))))
      )
      (ATOI (GETVAR "CECOLOR"))
    )
    -150
    32
  )
  (PRINC)
)

(DEFUN reactor:grdisplaytest ()
  (princ "REACTOR")
  (REDRAW)
  (gtoverlay:displaypoint
    (_toprightpoint)
    (STRCAT
      "\nDATE: "
      (gtmisc:getdate)
      "\nTIME: "
      (gtmisc:gettime)
      "\n________________\n"
      (APPLY
	(FUNCTION STRCAT)
	(CDR
	  (APPLY
	    (FUNCTION APPEND)
	    (MAPCAR
	      (FUNCTION
		(LAMBDA	(v)
		  (LIST	"\n"
			(STRCASE v)
			": "
			(VL-PRINC-TO-STRING (GETVAR v))
		  )
		)
	      )
	      '("CLAYER" "CECOLOR" "CELTYPE" "DIMSCALE" "OSMODE")
	    )
	  )
	)
      )
    )

    (IF	(OR (= (GETVAR "CECOLOR") "BYLAYER")
	    (= (GETVAR "CECOLOR") "BYBLOCK")
	)
      (cdr
	(assoc 62 (entget (tblobjname "layer" (getvar "CLAYER"))))
      )
      (ATOI (GETVAR "CECOLOR"))
    )
    -150
    32
  )
  (PRINC)
)


;;s: Screen Horizontal View points
;;c: current screen centre view port
;;d: 2D Point
(DEFUN _topleftpoint (/ s c d)
  (SETQ s (/ (GETVAR 'viewsize) 2.0))
  (SETQ c (GETVAR 'viewctr))
  (SETQ d (LIST (* s (APPLY (FUNCTION /) (GETVAR 'screensize))) s))
  (LIST	(CAR (MAPCAR (FUNCTION -) c d))
	(CADR (MAPCAR (FUNCTION +) c d))
	0.
  )
)


(DEFUN _toprightpoint ()
  (SETQ	across (* (GETVAR "VIEWSIZE")
		  (/ (CAR (GETVAR "SCREENSIZE"))
		     (CADR (GETVAR "SCREENSIZE"))
		  )
	       )
	left   (- (CAR (GETVAR "VIEWCTR")) (/ across 2.0))
	right  (+ (CAR (GETVAR "VIEWCTR")) (/ across 2.0))
	top    (+ (CADR (GETVAR "VIEWCTR")) (/ (GETVAR "VIEWSIZE") 2.0))
	bottom (- (CADR (GETVAR "VIEWCTR")) (/ (GETVAR "VIEWSIZE") 2.0))
  )
  (LIST right top 0.0)
)

(DEFUN gtoverlay:displaypoint (point string colour offsetx offsety)
  (
   (LAMBDA (s p)
     (GRVECS (gtoverlay:vector_text string colour)
	     (
	      (LAMBDA (s x y)
		(LIST
		  (LIST s 0. 0. x)
		  (LIST 0. s 0. y)
		  (LIST 0. 0. s 0.)
		  (LIST 0. 0. 0. 1.)
		)
	      )
	       s
	       (+ (CAR p) (* offsetx s))
	       (- (CADR p) (* offsety s))
	     )
     )
   )
    (/ (GETVAR 'viewsize) (CADR (GETVAR 'screensize)))
    (TRANS point 1 3)
  )
)
